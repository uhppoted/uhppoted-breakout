UHPPOTED-SSMP-MIB DEFINITIONS ::= BEGIN

IMPORTS
    MODULE-IDENTITY, OBJECT-TYPE, enterprises, Integer32
        FROM SNMPv2-SMI
    MODULE-COMPLIANCE, OBJECT-GROUP
        FROM SNMPv2-CONF;

uhppotedSSMP MODULE-IDENTITY
    LAST-UPDATED "202407290000Z"
    ORGANIZATION "github.com/uhppoted"
    CONTACT-INFO    
        "email: uhppoted.development@gmail.com"
    DESCRIPTION
        "MIB objects for the uhppoted breakout board"
    REVISION "202407290000Z"
        DESCRIPTION "First draft"
    ::= { enterprises 65536 }

internal   OBJECT IDENTIFIER ::= { uhppotedSSMP 0 }
system     OBJECT IDENTIFIER ::= { uhppotedSSMP 1 }
controller OBJECT IDENTIFIER ::= { uhppotedSSMP 2 }
doors      OBJECT IDENTIFIER ::= { uhppotedSSMP 3 }
inputs     OBJECT IDENTIFIER ::= { uhppotedSSMP 4 }
cards      OBJECT IDENTIFIER ::= { uhppotedSSMP 5 }
events     OBJECT IDENTIFIER ::= { uhppotedSSMP 6 }

door1     OBJECT IDENTIFIER ::= { doors 1 }
door2     OBJECT IDENTIFIER ::= { doors 2 }
door3     OBJECT IDENTIFIER ::= { doors 3 }
door4     OBJECT IDENTIFIER ::= { doors 4 }

event_indices OBJECT IDENTIFIER ::= { events 0 }

-- system
boardId OBJECT-TYPE
    SYNTAX      OCTET STRING (SIZE(0..32))
    MAX-ACCESS  read-only
    STATUS      current
    DESCRIPTION
        "An integer object representing the RP2040 board ID."
    ::= { system 1 }

-- controller
controllerId OBJECT-TYPE
    SYNTAX      Integer32 (0..2147483647)
    MAX-ACCESS  read-only
    STATUS      current
    DESCRIPTION
        "An integer object representing the controller ID."
    ::= { controller 1 }

controllerVersion OBJECT-TYPE
    SYNTAX      OCTET STRING (SIZE(2))
    MAX-ACCESS  read-only
    STATUS      current
    DESCRIPTION
        "A 2 byte octet string representing the controller firmware version (major,minor)."
    ::= { controller 2 }

controllerReleased OBJECT-TYPE
    SYNTAX      OCTET STRING (SIZE(8))
    MAX-ACCESS  read-only
    STATUS      current
    DESCRIPTION
        "An 8 byte octet string representing the controller firmware release date (YYYYMMDD)."
    ::= { controller 3 }

controllerAddress OBJECT-TYPE
    SYNTAX      OCTET STRING (SIZE(4))
    MAX-ACCESS  read-only
    STATUS      current
    DESCRIPTION
        "A 4 byte octet string representing the controller IPv4 address."
    ::= { controller 4 }

controllerNetmask OBJECT-TYPE
    SYNTAX      OCTET STRING (SIZE(4))
    MAX-ACCESS  read-only
    STATUS      current
    DESCRIPTION
        "A 4 byte octet string representing the controller IPv4 netmask."
    ::= { controller 5 }

controllerGateway OBJECT-TYPE
    SYNTAX      OCTET STRING (SIZE(4))
    MAX-ACCESS  read-only
    STATUS      current
    DESCRIPTION
        "A 4 byte octet string representing the controller IPv4 gateway address."
    ::= { controller 6 }

controllerMAC OBJECT-TYPE
    SYNTAX      OCTET STRING (SIZE(6))
    MAX-ACCESS  read-only
    STATUS      current
    DESCRIPTION
        "A 6 byte octet string representing the controller MAC address."
    ::= { controller 7 }

controllerDateTime OBJECT-TYPE
    SYNTAX      OCTET STRING (SIZE(6))
    MAX-ACCESS  read-only
    STATUS      current
    DESCRIPTION
        "A 19 byte octet string representing the controller date/time formatted YYYY-MM-dd HH:mm:ss."
    ::= { controller 8 }

controllerError OBJECT-TYPE
    SYNTAX      INTEGER (0..255)
    MAX-ACCESS  read-only
    STATUS      current
    DESCRIPTION
        "A 1 byte controller error code"
    ::= { controller 9 }

controllerSpecialInfo OBJECT-TYPE
    SYNTAX      Integer32 (0..2147483647)
    MAX-ACCESS  read-only
    STATUS      current
    DESCRIPTION
        "A 1 byte controller special info code"
    ::= { controller 10 }

controllerSequenceNumber OBJECT-TYPE
    SYNTAX      Integer32 (0..255)
    MAX-ACCESS  read-only
    STATUS      current
    DESCRIPTION
        "A uint32 message sequence number"
    ::= { controller 11 }

controllerEventsListener OBJECT-TYPE
    SYNTAX      OCTET STRING (SIZE(4))
    MAX-ACCESS  read-only
    STATUS      current
    DESCRIPTION
        "A 6 byte octet string representing the event listener IPv4 address:port."
    ::= { controller 12 }

controllerUploadInterval OBJECT-TYPE
    SYNTAX      Integer32 (0..255)
    MAX-ACCESS  read-only
    STATUS      current
    DESCRIPTION
        "An byte object representing the status + event auto-send interval (seconds)."
    ::= { controller 13 }

-- doors

-- door 1
door1Mode OBJECT-TYPE
    SYNTAX      INTEGER(0..3)
    MAX-ACCESS  read-only
    STATUS      current
    DESCRIPTION
        "'normally-open', 'normally-closed' or 'controlled'."
    ::= { door1 1 }

door1Delay OBJECT-TYPE
    SYNTAX      INTEGER (0..255)
    MAX-ACCESS  read-only
    STATUS      current
    DESCRIPTION
        "Door 1 unlock delay (seconds)."
    ::= { door1 2 }

door1Unlocked OBJECT-TYPE
    SYNTAX      INTEGER (0..1)
    MAX-ACCESS  read-only
    STATUS      current
    DESCRIPTION
        "Door 1 unlocked state."
    ::= { door1 3 }

door1Open OBJECT-TYPE
    SYNTAX      INTEGER (0..1)
    MAX-ACCESS  read-only
    STATUS      current
    DESCRIPTION
        "Door 1 open state."
    ::= { door1 4 }

door1Button OBJECT-TYPE
    SYNTAX      INTEGER (0..1)
    MAX-ACCESS  read-only
    STATUS      current
    DESCRIPTION
        "Door 1 button pressed."
    ::= { door1 5 }

-- door 2
door2Mode OBJECT-TYPE
    SYNTAX      INTEGER(0..3)
    MAX-ACCESS  read-only
    STATUS      current
    DESCRIPTION
        "'normally-open', 'normally-closed' or 'controlled'."
    ::= { door2 1 }

door2Delay OBJECT-TYPE
    SYNTAX      INTEGER (0..255)
    MAX-ACCESS  read-only
    STATUS      current
    DESCRIPTION
        "Door 2 unlock delay (seconds)."
    ::= { door2 2 }

door2Unlocked OBJECT-TYPE
    SYNTAX      INTEGER (0..1)
    MAX-ACCESS  read-only
    STATUS      current
    DESCRIPTION
        "Door 2 unlocked state."
    ::= { door2 3 }

door2Open OBJECT-TYPE
    SYNTAX      INTEGER (0..1)
    MAX-ACCESS  read-only
    STATUS      current
    DESCRIPTION
        "Door 2 open state."
    ::= { door2 4 }

door2Button OBJECT-TYPE
    SYNTAX      INTEGER (0..1)
    MAX-ACCESS  read-only
    STATUS      current
    DESCRIPTION
        "Door 2 button pressed."
    ::= { door2 5 }

-- door 3
door3Mode OBJECT-TYPE
    SYNTAX      INTEGER(0..3)
    MAX-ACCESS  read-only
    STATUS      current
    DESCRIPTION
        "'normally-open', 'normally-closed' or 'controlled'."
    ::= { door3 1 }

door3Delay OBJECT-TYPE
    SYNTAX      INTEGER (0..255)
    MAX-ACCESS  read-only
    STATUS      current
    DESCRIPTION
        "Door 3 unlock delay (seconds)."
    ::= { door3 2 }

door3Unlocked OBJECT-TYPE
    SYNTAX      INTEGER (0..1)
    MAX-ACCESS  read-only
    STATUS      current
    DESCRIPTION
        "Door 3 unlocked state."
    ::= { door3 3 }

door3Open OBJECT-TYPE
    SYNTAX      INTEGER (0..1)
    MAX-ACCESS  read-only
    STATUS      current
    DESCRIPTION
        "Door 3 open state."
    ::= { door3 4 }

door3Button OBJECT-TYPE
    SYNTAX      INTEGER (0..1)
    MAX-ACCESS  read-only
    STATUS      current
    DESCRIPTION
        "Door 3 button pressed."
    ::= { door3 5 }

-- door 4
door4Mode OBJECT-TYPE
    SYNTAX      INTEGER(0..3)
    MAX-ACCESS  read-only
    STATUS      current
    DESCRIPTION
        "'normally-open', 'normally-closed' or 'controlled'."
    ::= { door4 1 }

door4Delay OBJECT-TYPE
    SYNTAX      INTEGER (0..255)
    MAX-ACCESS  read-only
    STATUS      current
    DESCRIPTION
        "Door 4 unlock delay (seconds)."
    ::= { door4 2 }

door4Unlocked OBJECT-TYPE
    SYNTAX      INTEGER (0..1)
    MAX-ACCESS  read-only
    STATUS      current
    DESCRIPTION
        "Door 4 unlocked state."
    ::= { door4 3 }

door4Open OBJECT-TYPE
    SYNTAX      INTEGER (0..1)
    MAX-ACCESS  read-only
    STATUS      current
    DESCRIPTION
        "Door 4 open state."
    ::= { door4 4 }

door4Button OBJECT-TYPE
    SYNTAX      INTEGER (0..1)
    MAX-ACCESS  read-only
    STATUS      current
    DESCRIPTION
        "Door 4 button pressed."
    ::= { door4 5 }

-- inputs
inputTamperDetect OBJECT-TYPE
    SYNTAX      INTEGER(0..1)
    MAX-ACCESS  read-only
    STATUS      current
    DESCRIPTION
        "Tamper detect relay contact (normally closed)."
    ::= { inputs 1 }

inputFireAlarm OBJECT-TYPE
    SYNTAX      INTEGER (0..1)
    MAX-ACCESS  read-only
    STATUS      current
    DESCRIPTION
        "Fire alarm relay contact (normally closed)."
    ::= { inputs 2 }


-- cards


-- events

eventsFirst OBJECT-TYPE
    SYNTAX      Integer32 (0..2147483647)
    MAX-ACCESS  read-only
    STATUS      current
    DESCRIPTION
        "Index of first stored event"
    ::= { events_indices 1 }

eventsLast OBJECT-TYPE
    SYNTAX      Integer32 (0..2147483647)
    MAX-ACCESS  read-only
    STATUS      current
    DESCRIPTION
        "Index of last stored event"
    ::= { event_indices 2 }

-- groups
systemGroup OBJECT-GROUP
    OBJECTS { boardId }
    STATUS  current
    DESCRIPTION
        "System information."
    ::= { internal 1 }

controllerGroup OBJECT-GROUP
    OBJECTS { controllerId,
              controllerVersion,
              controllerReleased,
              controllerAddress,
              controllerNetmask,
              controllerGateway,
              controllerMAC,
              controllerDateTime,
              controllerError,
              controllerSpecialInfo,
              controllerSequenceNumber,
              controllerEventsListener,
              controllerUploadInterval }
    STATUS  current
    DESCRIPTION
        "Controller system information."
    ::= { internal 2 }

doorsGroup OBJECT-GROUP
    OBJECTS { door1Mode,
              door1Delay,
              door1Unlocked,
              door1Open,
              door1Button,
            
              door2Mode,
              door2Delay,
              door2Unlocked,
              door2Open,
              door2Button,
            
              door3Mode,
              door3Delay,
              door3Unlocked,
              door3Open,
              door3Button,
            
              door4Mode,
              door4Delay,
              door4Unlocked,
              door4Open,
              door4Button }
    STATUS  current
    DESCRIPTION
        "Door configuration and state information."
    ::= { internal 3 }

inputsGroup OBJECT-GROUP
    OBJECTS { inputTamperDetect,
              inputFireAlarm }
    STATUS  current
    DESCRIPTION
        "Input state information."
    ::= { internal 4 }

cardsGroup OBJECT-GROUP
    OBJECTS { }
    STATUS  current
    DESCRIPTION
        "Cards list."
    ::= { internal 5 }

eventsGroup OBJECT-GROUP
    OBJECTS { eventsFirst,
              eventsLast }
    STATUS  current
    DESCRIPTION
        "Events list."
    ::= { internal 6 }


-- compliance
compliance MODULE-COMPLIANCE
    STATUS  current
    DESCRIPTION
        "The compliance statement for the system, controller, doors, inputs, cards and events groups."
    MODULE  -- this module
    MANDATORY-GROUPS { systemGroup,
                       controllerGroup,
                       doorsGroup,
                       inputsGroup,
                       cardsGroup,
                       eventsGroup }
    ::= { internal 0 }

END
